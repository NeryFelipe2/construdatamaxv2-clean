(vl-load-com)
(defun C:TESTE_AEC (/ doc msp obj objname count_struct count_pipe count_other f rim nome)
  (setq doc (vla-get-ActiveDocument (vlax-get-acad-object)))
  (setq msp (vla-get-ModelSpace doc))
  (setq count_struct 0 count_pipe 0 count_other 0)
  (setq f (open "C:/Users/felip/Downloads/NOVA NS Versao 5/_tmp_dwg/TESTE_AEC_RESULT.txt" "w"))
  (write-line (strcat "TOTAL_ENTIDADES=" (itoa (vla-get-Count msp))) f)
  (vlax-for obj msp
    (setq objname (vl-catch-all-apply 'vla-get-ObjectName (list obj)))
    (if (vl-catch-all-error-p objname) (setq objname "ERR"))
    (cond
      ((and (vl-string-search "Aecc" objname) (vl-string-search "Struct" objname))
        (setq count_struct (1+ count_struct))
        (setq nome (vl-catch-all-apply 'vlax-get-property (list obj 'Name)))
        (setq rim (vl-catch-all-apply 'vlax-get-property (list obj 'RimElevation)))
        (write-line (strcat "STRUCT=" objname
          "|NAME=" (if (vl-catch-all-error-p nome) (strcat "ERR:" (vl-catch-all-error-message nome)) (vl-princ-to-string nome))
          "|RIM=" (if (vl-catch-all-error-p rim) (strcat "ERR:" (vl-catch-all-error-message rim)) (rtos rim 2 4))
        ) f)
      )
      ((and (vl-string-search "Aecc" objname) (vl-string-search "Pipe" objname))
        (setq count_pipe (1+ count_pipe))
        (write-line (strcat "PIPE=" objname) f)
      )
      ((vl-string-search "Aecc" objname)
        (setq count_other (1+ count_other))
        (write-line (strcat "OTHER=" objname) f)
      )
    )
  )
  (write-line (strcat "STRUCTS=" (itoa count_struct)) f)
  (write-line (strcat "PIPES=" (itoa count_pipe)) f)
  (write-line (strcat "OTHER_AECC=" (itoa count_other)) f)
  (write-line "DONE=1" f)
  (close f)
  (princ (strcat "\n[TESTE] Structs=" (itoa count_struct) " Pipes=" (itoa count_pipe)))
  (princ)
)
(C:TESTE_AEC)
